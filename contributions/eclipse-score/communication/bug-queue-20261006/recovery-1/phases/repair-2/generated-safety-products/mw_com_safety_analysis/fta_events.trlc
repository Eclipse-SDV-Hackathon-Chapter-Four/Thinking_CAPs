// GENERATED by puml_cli from FTA diagrams -- do not edit
package mw_com_fta

import ScoreReq
import Communication

// callback_invoked_with_wrong_data_fta.puml:26
ScoreReq.RootCause ActivelyManipulateByProgrammParts {
  title = "Actively manipulate by programm parts"
  diagram = "callback_invoked_with_wrong_data_fta.puml"
  line = 26
  failure_modes = [Communication.CallbackInvokedWithWrongData]
}

// only_partially_notifies_user_fta.puml:27
ScoreReq.RootCause AlgorithmicBug {
  title = "Algorithmic Bug"
  diagram = "only_partially_notifies_user_fta.puml"
  line = 27
  failure_modes = [Communication.SendingEventOnlyPartiallyNotifiesConsumer]
}

// to_few_memory_allocated_fta.puml:42
ScoreReq.RootCause AllocateClaimsToFewMemory {
  title = "Allocate claims to few memory"
  diagram = "to_few_memory_allocated_fta.puml"
  line = 42
  failure_modes = [Communication.TooFewMemoryAllocated]
}

// skeleton_offered_wrong_binding_fta.puml:26
ScoreReq.RootCause BindingSelectionFaulty {
  title = "Binding selection faulty"
  diagram = "skeleton_offered_wrong_binding_fta.puml"
  line = 26
  failure_modes = [Communication.ServiceOfferedOnWrongBinding]
}

// call_blocks_fta.puml:21
ScoreReq.RootCause BlocksOnCaller {
  title = "Method call blocks in message-passing at the caller side -> send blocked"
  diagram = "call_blocks_fta.puml"
  line = 21
  failure_modes = [Communication.MethodCallBlocksLongerThanExpected]
}

// allocate_in_wrong_memory_fta.puml:51
ScoreReq.RootCause BrokenAllocator {
  title = "Broken allocator"
  diagram = "allocate_in_wrong_memory_fta.puml"
  line = 51
  failure_modes = [Communication.MemoryAllocatedInWrongSection]
}

// call_blocks_fta.puml:23
ScoreReq.RootCause CallBlocksOnCallee {
  title = "Method call blocks in reply at the callee side -> send blocked "
  diagram = "call_blocks_fta.puml"
  line = 23
  failure_modes = [Communication.MethodCallBlocksLongerThanExpected]
}

// call_blocks_fta.puml:22
ScoreReq.RootCause CallBlocksOnUserHandler {
  title = "Method call blocks in user-handler at the callee side"
  diagram = "call_blocks_fta.puml"
  line = 22
  failure_modes = [Communication.MethodCallBlocksLongerThanExpected]
}

// wrong_in_args_provided_fta.puml:24
ScoreReq.RootCause CallSignalledBeforeInArgsCompletelyProvided {
  title = "Call signalled before InArgs completely provided"
  diagram = "wrong_in_args_provided_fta.puml"
  line = 24
  failure_modes = [Communication.WrongMethodInArgsProvided]
}

// callback_invoked_with_wrong_data_fta.puml:25
ScoreReq.RootCause CallbackDangling {
  title = "Callback dangling"
  diagram = "callback_invoked_with_wrong_data_fta.puml"
  line = 25
  failure_modes = [Communication.CallbackInvokedWithWrongData]
}

// callback_not_invoked_despite_samples_available_fta.puml:31
ScoreReq.RootCause CallbackIsNotStoredCorrectly {
  title = "Callback is not stored correctly"
  diagram = "callback_not_invoked_despite_samples_available_fta.puml"
  line = 31
  failure_modes = [Communication.CallbackNotInvokedDespiteSamplesAvailable]
}

// start_find_service_callback_is_redundantly_called_fta.puml:22
ScoreReq.RootCause CalledEventhoughStopfindserviceHasBeenCalled {
  title = "Called eventhough StopFindService has been called"
  diagram = "start_find_service_callback_is_redundantly_called_fta.puml"
  line = 22
  failure_modes = [Communication.StartFindServiceCallbackCalledUnexpectedly]
}

// start_find_service_callback_is_redundantly_called_fta.puml:21
ScoreReq.RootCause CalledReduandently {
  title = "Called reduandently"
  diagram = "start_find_service_callback_is_redundantly_called_fta.puml"
  line = 21
  failure_modes = [Communication.StartFindServiceCallbackCalledUnexpectedly]
}

// wrong_results_provided_fta.puml:28
ScoreReq.RootCause CalleeConcurrentlyUpdatesResultAfterSignaling {
  title = "Callee concurrently updates result after signaling it"
  diagram = "wrong_results_provided_fta.puml"
  line = 28
  failure_modes = [Communication.WrongResultsProvided]
}

// wrong_results_provided_fta.puml:27
ScoreReq.RootCause CalleeProvidedResultInWrongLayout {
  title = "Callee provided result in wrong layout"
  diagram = "wrong_results_provided_fta.puml"
  line = 27
  failure_modes = [Communication.WrongResultsProvided]
}

// wrong_results_provided_fta.puml:25
ScoreReq.RootCause CalleeProvidedResultInWrongLocation {
  title = "Callee provided result in wrong location"
  diagram = "wrong_results_provided_fta.puml"
  line = 25
  failure_modes = [Communication.WrongResultsProvided]
}

// wrong_results_provided_fta.puml:24
ScoreReq.RootCause CalleeSignalledCallFinishedBeforeResultComplete {
  title = "Callee signalled call finished before or without providing result completely"
  diagram = "wrong_results_provided_fta.puml"
  line = 24
  failure_modes = [Communication.WrongResultsProvided]
}

// wrong_in_args_used_fta.puml:26
ScoreReq.RootCause CalleeUsedInArgsBeforeBeingProvided {
  title = "Callee used InArgs before being provided"
  diagram = "wrong_in_args_used_fta.puml"
  line = 26
  failure_modes = [Communication.WrongMethodInArgsUsed]
}

// wrong_in_args_used_fta.puml:25
ScoreReq.RootCause CalleeUsedInArgsFromWrongLocation {
  title = "Callee used InArgs from wrong location"
  diagram = "wrong_in_args_used_fta.puml"
  line = 25
  failure_modes = [Communication.WrongMethodInArgsUsed]
}

// wrong_in_args_used_fta.puml:28
ScoreReq.RootCause CalleeUsedInArgsInWrongLayout {
  title = "Callee used InArgs in wrong layout"
  diagram = "wrong_in_args_used_fta.puml"
  line = 28
  failure_modes = [Communication.WrongMethodInArgsUsed]
}

// wrong_in_args_used_fta.puml:29
ScoreReq.RootCause CalleeUsedInArgsWhileConcurrentlyUpdated {
  title = "Callee used InArgs while concurrently updated"
  diagram = "wrong_in_args_used_fta.puml"
  line = 29
  failure_modes = [Communication.WrongMethodInArgsUsed]
}

// wrong_in_args_provided_fta.puml:25
ScoreReq.RootCause CallerProvidedInArgsInWrongLocation {
  title = "Caller provided InArgs in wrong location"
  diagram = "wrong_in_args_provided_fta.puml"
  line = 25
  failure_modes = [Communication.WrongMethodInArgsProvided]
}

// wrong_results_used_fta.puml:23
ScoreReq.RootCause CallerUsedResultBeforeFullyProvided {
  title = "Caller used result before fully provided"
  diagram = "wrong_results_used_fta.puml"
  line = 23
  failure_modes = [Communication.WrongReturnValueUsed]
}

// wrong_results_used_fta.puml:21
ScoreReq.RootCause CallerUsedResultFromWrongLocation {
  title = "Caller used result from wrong location"
  diagram = "wrong_results_used_fta.puml"
  line = 21
  failure_modes = [Communication.WrongReturnValueUsed]
}

// wrong_results_used_fta.puml:22
ScoreReq.RootCause CallerUsedResultInWrongLayout {
  title = "Caller used result in wrong layout"
  diagram = "wrong_results_used_fta.puml"
  line = 22
  failure_modes = [Communication.WrongReturnValueUsed]
}

// wrong_results_used_fta.puml:24
ScoreReq.RootCause CallerUsedResultWhileConcurrentlyUpdated {
  title = "Caller used result while concurrently updated"
  diagram = "wrong_results_used_fta.puml"
  line = 24
  failure_modes = [Communication.WrongReturnValueUsed]
}

// does_not_free_resources_on_destruction_fta.puml:24
ScoreReq.RootCause ChangingStateFails {
  title = "Changing state fails"
  diagram = "does_not_free_resources_on_destruction_fta.puml"
  line = 24
  failure_modes = [Communication.DoesNotFreeResourcesOnDestruction]
}

// the_size_returned_is_bigger_then_actual_value_fta.puml:25
ScoreReq.RootCause ConsumerLookedUpSizeInWrongLocation {
  title = "Consumer looked up size in wrong location"
  diagram = "the_size_returned_is_bigger_then_actual_value_fta.puml"
  line = 25
  failure_modes = [Communication.TheSizeReturnedIsBiggerThenTheActualValue]
}

// to_few_memory_allocated_fta.puml:36
ScoreReq.RootCause ConsumerUsesAnOlderSlotThanHeAlreadyHasBlockedInThePreviousAccess {
  title = "Consumer uses an older slot, than he already has blocked in the previous access"
  diagram = "to_few_memory_allocated_fta.puml"
  line = 36
  failure_modes = [Communication.TooFewMemoryAllocated]
}

// does_not_free_resources_after_usage_fta.puml:23
ScoreReq.RootCause CopyOnSendDoesNotDestroySampleallocateeptr {
  title = "Copy on send does not destroy SampleAllocateePtr"
  diagram = "does_not_free_resources_after_usage_fta.puml"
  line = 23
  failure_modes = [Communication.SendingEventDoesNotFreeResources]
}

// allocate_in_wrong_memory_fta.puml:52
ScoreReq.RootCause DataTypeItselfIsAllocatedOnStack {
  title = "Data-Type itself is allocated on stack"
  diagram = "allocate_in_wrong_memory_fta.puml"
  line = 52
  failure_modes = [Communication.MemoryAllocatedInWrongSection]
}

// stop_offer_state_inconsistent_fta.puml:25
ScoreReq.RootCause DependentPrepareOfferFailed {
  title = "PrepareOffer on dependent elements failed"
  diagram = "stop_offer_state_inconsistent_fta.puml"
  line = 25
  failure_modes = [Communication.StopOfferInconsistent]
}

// stop_offer_state_inconsistent_fta.puml:24
ScoreReq.RootCause DependentPrepareOfferNotCalled {
  title = "PrepareOffer on dependent elements not called"
  diagram = "stop_offer_state_inconsistent_fta.puml"
  line = 24
  failure_modes = [Communication.StopOfferInconsistent]
}

// does_not_free_resources_after_usage_fta.puml:24
ScoreReq.RootCause DestructionOfSampleallocateeptrDoesNotTriggerStateChange {
  title = "Destruction of SampleAllocateePtr does not trigger state change"
  diagram = "does_not_free_resources_after_usage_fta.puml"
  line = 24
  failure_modes = [Communication.SendingEventDoesNotFreeResources]
}

// skeleton_not_offered_fta.puml:34
ScoreReq.RootCause DifferentlyConfiguredBetweenSkletonAndProxySide {
  title = "Differently configured between skleton and proxy side"
  diagram = "skeleton_not_offered_fta.puml"
  line = 34
  failure_modes = [Communication.ServiceNotOffered]
}

// changes_user_data_fta.puml:31
ScoreReq.RootCause DirectAccessToDataViaAllocateePtr {
  title = "Direct access to data"
  diagram = "changes_user_data_fta.puml"
  line = 31
  failure_modes = [Communication.SendingEventChangesUserData]
}

// changes_user_data_fta.puml:22
ScoreReq.RootCause DirectAccessToDataViaCopy {
  title = "Direct access to data"
  diagram = "changes_user_data_fta.puml"
  line = 22
  failure_modes = [Communication.SendingEventChangesUserData]
}

// failure_freeing_resources_on_destruction_fta.puml:21
ScoreReq.RootCause DoesNotFreeMethodSignatureElement {
  title = "Does not free method signature element"
  diagram = "failure_freeing_resources_on_destruction_fta.puml"
  line = 21
  failure_modes = [Communication.MethodSignatureElementPtrFailsToFree]
}

// subscribe_to_wrong_event_fta.puml:23
ScoreReq.RootCause EventFieldIdReferencesWrongStorage {
  title = "Event/Field ID references wrong storage."
  diagram = "subscribe_to_wrong_event_fta.puml"
  line = 23
  failure_modes = [Communication.SubscribeToWrongEvent]
}

// subscribe_to_wrong_event_fta.puml:22
ScoreReq.RootCause EventFieldNameMappingClash {
  title = "Event/Field name mapping clash"
  diagram = "subscribe_to_wrong_event_fta.puml"
  line = 22
  failure_modes = [Communication.SubscribeToWrongEvent]
}

// callback_invoked_with_wrong_data_fta.puml:30
ScoreReq.RootCause EventfqidWronglyConstructed {
  title = "EventFqId wrongly constructed"
  diagram = "callback_invoked_with_wrong_data_fta.puml"
  line = 30
  failure_modes = [Communication.CallbackInvokedWithWrongData]
}

// does_not_unsubscribe_fta.puml:20
ScoreReq.RootCause ExplicitUnsubscribeByUserFailed {
  title = "Explicit unsubscribe by user failed"
  diagram = "does_not_unsubscribe_fta.puml"
  line = 20
  failure_modes = [Communication.DoesNotUnsubscribe]
}

// in_memory_configuration_wrong_fta.puml:24
ScoreReq.RootCause FileCorrupted {
  title = "File corrupted"
  diagram = "in_memory_configuration_wrong_fta.puml"
  line = 24
  failure_modes = [Communication.InMemoryConfigurationWrong]
}

// service_offered_under_wrong_id_fta.puml:30
ScoreReq.RootCause FilenameCreationFromConfigFailed {
  title = "Filename creation from config failed"
  diagram = "service_offered_under_wrong_id_fta.puml"
  line = 30
  failure_modes = [Communication.ServiceOfferedUnderWrongIds]
}

// allocate_in_wrong_memory_fta.puml:45
ScoreReq.RootCause ForwardedTheWrongSharedMemorySegmentFromTheBeginning {
  title = "Forwarded the wrong shared memory segment from the beginning"
  diagram = "allocate_in_wrong_memory_fta.puml"
  line = 45
  failure_modes = [Communication.MemoryAllocatedInWrongSection]
}

// changes_user_data_fta.puml:25
ScoreReq.RootCause GenericTraceapiChangesData {
  title = "Generic TraceAPI changes data"
  diagram = "changes_user_data_fta.puml"
  line = 25
  failure_modes = [Communication.SendingEventChangesUserData]
}

// to_few_memory_allocated_fta.puml:32
ScoreReq.RootCause HoldsMoreSampleptrThanAnnounced {
  title = "Holds more SamplePtr than announced"
  diagram = "to_few_memory_allocated_fta.puml"
  line = 32
  failure_modes = [Communication.TooFewMemoryAllocated]
}

// to_few_memory_allocated_fta.puml:33
ScoreReq.RootCause HoldsMoreSampleptrThanConfigured {
  title = "Holds more SamplePtr than configured"
  diagram = "to_few_memory_allocated_fta.puml"
  line = 33
  failure_modes = [Communication.TooFewMemoryAllocated]
}

// wrong_in_args_used_fta.puml:30
ScoreReq.RootCause InArgsCorruptedBy3rdParty {
  title = "InArgs corrupted by 3d party"
  diagram = "wrong_in_args_used_fta.puml"
  line = 30
  failure_modes = [Communication.WrongMethodInArgsUsed]
}

// wrong_in_args_provided_fta.puml:30
ScoreReq.RootCause InArgsUpdateAfterCall {
  title = "Caller updates InArgs concurrently after call signalling"
  diagram = "wrong_in_args_provided_fta.puml"
  line = 30
  failure_modes = [Communication.WrongMethodInArgsProvided]
}

// wrong_in_args_provided_fta.puml:29
ScoreReq.RootCause InArgsWrongLayout {
  title = "Caller provided InArgs in wrong layout"
  diagram = "wrong_in_args_provided_fta.puml"
  line = 29
  failure_modes = [Communication.WrongMethodInArgsProvided]
}

// does_not_free_resources_on_destruction_fta.puml:25
ScoreReq.RootCause IncreasingDecreasingRefCountFails {
  title = "Increasing / Decreasing ref-count fails"
  diagram = "does_not_free_resources_on_destruction_fta.puml"
  line = 25
  failure_modes = [Communication.DoesNotFreeResourcesOnDestruction]
}

// start_find_service_callback_is_redundantly_called_fta.puml:26
ScoreReq.RootCause InotifyReturnsWrongInformation {
  title = "Inotify returns wrong information"
  diagram = "start_find_service_callback_is_redundantly_called_fta.puml"
  line = 26
  failure_modes = [Communication.StartFindServiceCallbackCalledUnexpectedly]
}

// skeleton_not_offered_fta.puml:33
ScoreReq.RootCause InstanceSpecifierResolutionBrokenNotOffered {
  title = "Instance Specifier resolution broken"
  diagram = "skeleton_not_offered_fta.puml"
  line = 33
  failure_modes = [Communication.ServiceNotOffered]
}

// skeleton_offered_wrong_binding_fta.puml:23
ScoreReq.RootCause InstanceSpecifierResolutionBrokenWrongBinding {
  title = "Instance Specifier resolution broken"
  diagram = "skeleton_offered_wrong_binding_fta.puml"
  line = 23
  failure_modes = [Communication.ServiceOfferedOnWrongBinding]
}

// service_offered_under_wrong_id_fta.puml:23
ScoreReq.RootCause InstanceSpecifierResolutionFaulty {
  title = "Instance Specifier resolution faulty"
  diagram = "service_offered_under_wrong_id_fta.puml"
  line = 23
  failure_modes = [Communication.ServiceOfferedUnderWrongIds]
}

// creation_of_skeleton_not_possible_fta.puml:24
ScoreReq.RootCause InstanceSpecifierResolutionLogicBroken {
  title = "Instance Specifier resolution logic broken"
  diagram = "creation_of_skeleton_not_possible_fta.puml"
  line = 24
  failure_modes = [Communication.CreationOfSkeletonNotPossible]
}

// wrong_service_found_fta.puml:26
ScoreReq.RootCause InstancespecifierResolvedToWrongInstanceidentifier {
  title = "InstanceSpecifier resolved to wrong InstanceIdentifier"
  diagram = "wrong_service_found_fta.puml"
  line = 26
  failure_modes = [Communication.WrongServiceFound]
}

// to_few_memory_allocated_fta.puml:38
ScoreReq.RootCause IssueInLockFreeSychronization {
  title = "Issue in Lock-free Sychronization"
  diagram = "to_few_memory_allocated_fta.puml"
  line = 38
  failure_modes = [Communication.TooFewMemoryAllocated]
}

// in_memory_configuration_wrong_fta.puml:25
ScoreReq.RootCause JsonParserBroken {
  title = "JSON Parser broken"
  diagram = "in_memory_configuration_wrong_fta.puml"
  line = 25
  failure_modes = [Communication.InMemoryConfigurationWrong]
}

// points_to_wrong_data_fta.puml:22
ScoreReq.RootCause LifeCycleIssuesElementPtr {
  title = "Life-Cycle issues"
  diagram = "points_to_wrong_data_fta.puml"
  line = 22
  failure_modes = [Communication.MethodSignatureElementPtrWrongTarget]
}

// returns_wrong_data_fta.puml:22
ScoreReq.RootCause LifeCycleIssuesSamplePtr {
  title = "Life-Cycle issues"
  diagram = "returns_wrong_data_fta.puml"
  line = 22
  failure_modes = [Communication.ReturnsWrongData]
}

// to_few_memory_allocated_fta.puml:27
ScoreReq.RootCause LiteralyWrongNumberOfSlotsReserved {
  title = "Literaly wrong number of slots reserved"
  diagram = "to_few_memory_allocated_fta.puml"
  line = 27
  failure_modes = [Communication.TooFewMemoryAllocated]
}

// in_memory_configuration_wrong_fta.puml:28
ScoreReq.RootCause ManipulateReadData {
  title = "Manipulate read data"
  diagram = "in_memory_configuration_wrong_fta.puml"
  line = 28
  failure_modes = [Communication.InMemoryConfigurationWrong]
}

// to_few_memory_allocated_fta.puml:22
ScoreReq.RootCause MappingFromActualEventidToEventTypeIncorrect {
  title = "Mapping from actual EventID to Event-Type incorrect"
  diagram = "to_few_memory_allocated_fta.puml"
  line = 22
  failure_modes = [Communication.TooFewMemoryAllocated]
}

// subscribe_with_wrong_max_sample_count_fta.puml:20
ScoreReq.RootCause MessagePassingCorruptsTheMaxSampleValue {
  title = "Message passing corrupts the max. sample value"
  diagram = "subscribe_with_wrong_max_sample_count_fta.puml"
  line = 20
  failure_modes = [Communication.SubscribeWithWrongMaxSampleCount]
}

// wrong_method_called_fta.puml:26
ScoreReq.RootCause MethodIdCorrupted {
  title = "MethodId corrupted"
  diagram = "wrong_method_called_fta.puml"
  line = 26
  failure_modes = [Communication.WrongMethodCalled]
}

// allocate_in_wrong_memory_fta.puml:40
ScoreReq.RootCause MiddlewareProvidedTypeIsWrong {
  title = "Middleware provided type is wrong"
  diagram = "allocate_in_wrong_memory_fta.puml"
  line = 40
  failure_modes = [Communication.MemoryAllocatedInWrongSection]
}

// to_few_memory_allocated_fta.puml:39
ScoreReq.RootCause MoreThanOneSampleallocateeptrInParallel {
  title = "More than one SampleAllocateePtr in parallel"
  diagram = "to_few_memory_allocated_fta.puml"
  line = 39
  failure_modes = [Communication.TooFewMemoryAllocated]
}

// to_few_memory_allocated_fta.puml:45
ScoreReq.RootCause NecessarySizeCalculationRetreivesWrongValue {
  title = "Necessary size calculation retreives wrong value"
  diagram = "to_few_memory_allocated_fta.puml"
  line = 45
  failure_modes = [Communication.TooFewMemoryAllocated]
}

// no_resources_freed_fta.puml:22
ScoreReq.RootCause NoUnmapOnDestruction {
  title = "No unmap on destruction"
  diagram = "no_resources_freed_fta.puml"
  line = 22
  failure_modes = [Communication.NoResourcesFreed]
}

// only_partially_offered_fta.puml:25
ScoreReq.RootCause NotAllEventsArePopulated {
  title = "Not all events are populated"
  diagram = "only_partially_offered_fta.puml"
  line = 25
  failure_modes = [Communication.ServiceOnlyPartiallyOffered]
}

// skeleton_not_offered_fta.puml:23
ScoreReq.RootCause NotCreatedAtAll {
  title = "Not created at all"
  diagram = "skeleton_not_offered_fta.puml"
  line = 23
  failure_modes = [Communication.ServiceNotOffered]
}

// skeleton_not_offered_without_initial_fieled_value_fta.puml:21
ScoreReq.RootCause OfferCallDidNotCheckIfUserProvidedFieldValues {
  title = "Offer call did not check, if user provided field values"
  diagram = "skeleton_not_offered_without_initial_fieled_value_fta.puml"
  line = 21
  failure_modes = [Communication.ServiceOfferedWithoutInitialFieldValue]
}

// stop_offer_state_inconsistent_fta.puml:22
ScoreReq.RootCause OfferStateInconsistent {
  title = "Offer State inconsistent"
  diagram = "stop_offer_state_inconsistent_fta.puml"
  line = 22
  failure_modes = [Communication.StopOfferInconsistent]
}

// allocate_in_wrong_memory_fta.puml:48
ScoreReq.RootCause OffsetPtrCorruption {
  title = "Offset PTR corruption"
  diagram = "allocate_in_wrong_memory_fta.puml"
  line = 48
  failure_modes = [Communication.MemoryAllocatedInWrongSection]
}

// in_memory_configuration_wrong_fta.puml:29
ScoreReq.RootCause OmitReadingOfRelevantElements {
  title = "Omit reading of relevant elements"
  diagram = "in_memory_configuration_wrong_fta.puml"
  line = 29
  failure_modes = [Communication.InMemoryConfigurationWrong]
}

// callback_invoked_with_wrong_data_fta.puml:36
ScoreReq.RootCause OrderingWrong {
  title = "Ordering wrong"
  diagram = "callback_invoked_with_wrong_data_fta.puml"
  line = 36
  failure_modes = [Communication.CallbackInvokedWithWrongData]
}

// service_offered_under_wrong_id_fta.puml:31
ScoreReq.RootCause OsCreatesFileWithWrongName {
  title = "OS creates file with wrong name"
  diagram = "service_offered_under_wrong_id_fta.puml"
  line = 31
  failure_modes = [Communication.ServiceOfferedUnderWrongIds]
}

// skeleton_not_offered_fta.puml:29
ScoreReq.RootCause OsRelatedFunctionalityFailed {
  title = "OS related functionality failed"
  diagram = "skeleton_not_offered_fta.puml"
  line = 29
  failure_modes = [Communication.ServiceNotOffered]
}

// failure_freeing_resources_on_destruction_fta.puml:23
ScoreReq.RootCause OverwriteOfElementInUse {
  title = "Overwrite of element in use"
  diagram = "failure_freeing_resources_on_destruction_fta.puml"
  line = 23
  failure_modes = [Communication.MethodSignatureElementPtrFailsToFree]
}

// does_not_unsubscribe_fta.puml:21
ScoreReq.RootCause ProxyCrashesWithoutUnsubscription {
  title = "Proxy crashes without unsubscription"
  diagram = "does_not_unsubscribe_fta.puml"
  line = 21
  failure_modes = [Communication.DoesNotUnsubscribe]
}

// allocate_in_wrong_memory_fta.puml:53
ScoreReq.RootCause ProxyIdOverwritten {
  title = "Proxy ID overwritten"
  diagram = "allocate_in_wrong_memory_fta.puml"
  line = 53
  failure_modes = [Communication.MemoryAllocatedInWrongSection]
}

// callback_invoked_with_wrong_data_fta.puml:24
ScoreReq.RootCause PtrDangling {
  title = "PTR dangling"
  diagram = "callback_invoked_with_wrong_data_fta.puml"
  line = 24
  failure_modes = [Communication.CallbackInvokedWithWrongData]
}

// only_partially_notifies_user_fta.puml:22
ScoreReq.RootCause ReceiveErrorOnRegistration {
  title = "Receive error on registration"
  diagram = "only_partially_notifies_user_fta.puml"
  line = 22
  failure_modes = [Communication.SendingEventOnlyPartiallyNotifiesConsumer]
}

// points_to_wrong_data_fta.puml:27
ScoreReq.RootCause ReferencesInvalidMemory {
  title = "References invalid memory"
  diagram = "points_to_wrong_data_fta.puml"
  line = 27
  failure_modes = [Communication.MethodSignatureElementPtrWrongTarget]
}

// points_to_wrong_data_fta.puml:26
ScoreReq.RootCause ReferencesValidMemoryInsideSHM {
  title = "References valid memory inside shared-memory"
  diagram = "points_to_wrong_data_fta.puml"
  line = 26
  failure_modes = [Communication.MethodSignatureElementPtrWrongTarget]
}

// points_to_wrong_data_fta.puml:25
ScoreReq.RootCause ReferencesValidMemoryOutsideSHM {
  title = "References valid memory outside shared-memory"
  diagram = "points_to_wrong_data_fta.puml"
  line = 25
  failure_modes = [Communication.MethodSignatureElementPtrWrongTarget]
}

// to_few_memory_allocated_fta.puml:37
ScoreReq.RootCause RetryLogicNotBulletProof {
  title = "Retry-logic not bullet proof"
  diagram = "to_few_memory_allocated_fta.puml"
  line = 37
  failure_modes = [Communication.TooFewMemoryAllocated]
}

// offer_not_stopped_in_sd_fta.puml:25
ScoreReq.RootCause SDClientMarkerFileNotFound {
  title = "Marker File Not found"
  diagram = "offer_not_stopped_in_sd_fta.puml"
  line = 25
  failure_modes = [Communication.StopOfferNotStoppedInSD]
}

// offer_not_stopped_in_sd_fta.puml:26
ScoreReq.RootCause SDClientMarkerFileWrongPath {
  title = "Marker File Wrong path"
  diagram = "offer_not_stopped_in_sd_fta.puml"
  line = 26
  failure_modes = [Communication.StopOfferNotStoppedInSD]
}

// offer_stopped_for_wrong_instance_in_sd_fta.puml:21
ScoreReq.RootCause SDClientWrongMarkerFile {
  title = "Service Discovery Client deletes wrong marker file"
  diagram = "offer_stopped_for_wrong_instance_in_sd_fta.puml"
  line = 21
  failure_modes = [Communication.StopOfferWrongInstanceStoppedInSD]
}

// offer_not_stopped_in_sd_fta.puml:22
ScoreReq.RootCause SDFileDeletionFailure {
  title = "Marker File Deletion Failure"
  diagram = "offer_not_stopped_in_sd_fta.puml"
  line = 22
  failure_modes = [Communication.StopOfferNotStoppedInSD]
}

// offer_not_stopped_in_sd_fta.puml:23
ScoreReq.RootCause SDNotifyFailed {
  title = "inotify Event Failure"
  diagram = "offer_not_stopped_in_sd_fta.puml"
  line = 23
  failure_modes = [Communication.StopOfferNotStoppedInSD]
}

// offer_stopped_for_wrong_instance_in_sd_fta.puml:22
ScoreReq.RootCause SDNotifyWrongFD {
  title = "inotify notifies wrong FD"
  diagram = "offer_stopped_for_wrong_instance_in_sd_fta.puml"
  line = 22
  failure_modes = [Communication.StopOfferWrongInstanceStoppedInSD]
}

// shm_objects_unlink_failure_fta.puml:20
ScoreReq.RootCause SHMObjectWrongPath {
  title = "Wrong SHM path created"
  diagram = "shm_objects_unlink_failure_fta.puml"
  line = 20
  failure_modes = [Communication.StopOfferUnlinkWrongSHMObjects]
}

// only_partially_notifies_user_fta.puml:26
ScoreReq.RootCause ServerProcessCrash {
  title = "Server process crash"
  diagram = "only_partially_notifies_user_fta.puml"
  line = 26
  failure_modes = [Communication.SendingEventOnlyPartiallyNotifiesConsumer]
}

// shm_objects_unlink_failure_fta.puml:24
ScoreReq.RootCause ServiceInstanceUsageLockMechanismFailed {
  title = "Service instance usage lock mechanism failed"
  diagram = "shm_objects_unlink_failure_fta.puml"
  line = 24
  failure_modes = [Communication.StopOfferUnlinkWrongSHMObjects]
}

// shm_objects_unlink_failure_fta.puml:23
ScoreReq.RootCause ServiceInstanceUsageNotChecked {
  title = "Service instance usage not checked"
  diagram = "shm_objects_unlink_failure_fta.puml"
  line = 23
  failure_modes = [Communication.StopOfferUnlinkWrongSHMObjects]
}

// offers_already_offered_service_fta.puml:22
ScoreReq.RootCause ServiceWasAlreadyOfferedByOurProcess {
  title = "Service was already offered by our process"
  diagram = "offers_already_offered_service_fta.puml"
  line = 22
  failure_modes = [Communication.OffersAlreadyOfferedService]
}

// offers_already_offered_service_fta.puml:23
ScoreReq.RootCause ServiceWasAlreadyOfferedByPreviousDiedProcess {
  title = "Service was already offered by previous died process"
  diagram = "offers_already_offered_service_fta.puml"
  line = 23
  failure_modes = [Communication.OffersAlreadyOfferedService]
}

// service_is_found_but_does_not_exist_fta.puml:21
ScoreReq.RootCause ServiceWasOfferedButNotUnlikedOnStopOffer {
  title = "Service was offered, but not unliked on stop offer"
  diagram = "service_is_found_but_does_not_exist_fta.puml"
  line = 21
  failure_modes = [Communication.ServiceIsFoundButDoesNotExist]
}

// offers_already_offered_service_fta.puml:21
ScoreReq.RootCause ServiceWasOfferedByAnotherProcess {
  title = "Service was offered by another process"
  diagram = "offers_already_offered_service_fta.puml"
  line = 21
  failure_modes = [Communication.OffersAlreadyOfferedService]
}

// service_is_found_but_does_not_exist_fta.puml:22
ScoreReq.RootCause SharedMemoryIsOpenedEventhoughFileDoesNotExist {
  title = "Shared Memory is opened eventhough file does not exist"
  diagram = "service_is_found_but_does_not_exist_fta.puml"
  line = 22
  failure_modes = [Communication.ServiceIsFoundButDoesNotExist]
}

// service_is_found_but_does_not_exist_fta.puml:28
ScoreReq.RootCause SharedMemoryObjectDoesNotExist {
  title = "Shared Memory Object does not exist"
  diagram = "service_is_found_but_does_not_exist_fta.puml"
  line = 28
  failure_modes = [Communication.ServiceIsFoundButDoesNotExist]
}

// allocate_in_wrong_memory_fta.puml:44
ScoreReq.RootCause SharedMemoryResourceOpensWrongSharedMemorySegment {
  title = "Shared memory Resource opens wrong shared memory segment"
  diagram = "allocate_in_wrong_memory_fta.puml"
  line = 44
  failure_modes = [Communication.MemoryAllocatedInWrongSection]
}

// allocate_in_wrong_memory_fta.puml:27
ScoreReq.RootCause SharedMemoryResourceReturnsWrongProxy {
  title = "Shared Memory resource returns wrong proxy"
  diagram = "allocate_in_wrong_memory_fta.puml"
  line = 27
  failure_modes = [Communication.MemoryAllocatedInWrongSection]
}

// allocate_in_wrong_memory_fta.puml:31
ScoreReq.RootCause SharedMemoryRessourceNotForwarded {
  title = "Shared Memory ressource not forwarded"
  diagram = "allocate_in_wrong_memory_fta.puml"
  line = 31
  failure_modes = [Communication.MemoryAllocatedInWrongSection]
}

// skeleton_not_offered_fta.puml:28
ScoreReq.RootCause SharedMemorySegmentDoesNotTryToCreateSegment {
  title = "Shared Memory segment does not try to create segment."
  diagram = "skeleton_not_offered_fta.puml"
  line = 28
  failure_modes = [Communication.ServiceNotOffered]
}

// no_resources_freed_fta.puml:23
ScoreReq.RootCause SharedMemorySegmentIsNotUnlinked {
  title = "Shared Memory segment is not unlinked"
  diagram = "no_resources_freed_fta.puml"
  line = 23
  failure_modes = [Communication.NoResourcesFreed]
}

// skeleton_not_offered_fta.puml:30
ScoreReq.RootCause SharedMemorySegmentsAreCreatedUnderWrongName {
  title = "Shared Memory segments are created under wrong name"
  diagram = "skeleton_not_offered_fta.puml"
  line = 30
  failure_modes = [Communication.ServiceNotOffered]
}

// to_few_memory_allocated_fta.puml:46
ScoreReq.RootCause SharedMemoryTruncationFails {
  title = "Shared memory truncation fails"
  diagram = "to_few_memory_allocated_fta.puml"
  line = 46
  failure_modes = [Communication.TooFewMemoryAllocated]
}

// allocate_in_wrong_memory_fta.puml:28
ScoreReq.RootCause SharedmemoryfactoryReturnsWrongMemoryRessource {
  title = "SharedMemoryFactory returns wrong memory ressource"
  diagram = "allocate_in_wrong_memory_fta.puml"
  line = 28
  failure_modes = [Communication.MemoryAllocatedInWrongSection]
}

// the_size_returned_is_bigger_then_actual_value_fta.puml:24
ScoreReq.RootCause SizeWasManipulatedInSharedMemory {
  title = "Size was manipulated in Shared Memory"
  diagram = "the_size_returned_is_bigger_then_actual_value_fta.puml"
  line = 24
  failure_modes = [Communication.TheSizeReturnedIsBiggerThenTheActualValue]
}

// the_size_returned_is_bigger_then_actual_value_fta.puml:23
ScoreReq.RootCause SizeWasWronglySetInSharedMemory {
  title = "Size was wrongly set in Shared Memory"
  diagram = "the_size_returned_is_bigger_then_actual_value_fta.puml"
  line = 23
  failure_modes = [Communication.TheSizeReturnedIsBiggerThenTheActualValue]
}

// callback_invoked_with_wrong_data_fta.puml:40
ScoreReq.RootCause SlotAllocationSynchronisationWrongState {
  title = "Slot allocation synchronisation wrong"
  diagram = "callback_invoked_with_wrong_data_fta.puml"
  line = 40
  failure_modes = [Communication.CallbackInvokedWithWrongData]
}

// callback_invoked_with_wrong_data_fta.puml:38
ScoreReq.RootCause SlotAllocationSynchronisationWrongTimestamp {
  title = "Slot allocation synchronisation wrong"
  diagram = "callback_invoked_with_wrong_data_fta.puml"
  line = 38
  failure_modes = [Communication.CallbackInvokedWithWrongData]
}

// does_not_free_resources_on_destruction_fta.puml:26
ScoreReq.RootCause SlotReferenceBrokenEGNonValid {
  title = "Slot reference broken e.g. non-valid"
  diagram = "does_not_free_resources_on_destruction_fta.puml"
  line = 26
  failure_modes = [Communication.DoesNotFreeResourcesOnDestruction]
}

// creation_of_skeleton_not_possible_fta.puml:21
ScoreReq.RootCause StaticCreateFunctionReturnsAnError {
  title = "Static create function returns an error"
  diagram = "creation_of_skeleton_not_possible_fta.puml"
  line = 21
  failure_modes = [Communication.CreationOfSkeletonNotPossible]
}

// allocate_in_wrong_memory_fta.puml:32
ScoreReq.RootCause UserFehler {
  title = "User Fehler"
  diagram = "allocate_in_wrong_memory_fta.puml"
  line = 32
  failure_modes = [Communication.MemoryAllocatedInWrongSection]
}

// wrong_method_called_fta.puml:25
ScoreReq.RootCause UserMethodCallHandlerAssignmentWrong {
  title = "User Handler assignment wrong"
  diagram = "wrong_method_called_fta.puml"
  line = 25
  failure_modes = [Communication.WrongMethodCalled]
}

// allocate_in_wrong_memory_fta.puml:41
ScoreReq.RootCause UserProvidedTypeIsWrong {
  title = "User provided type is wrong"
  diagram = "allocate_in_wrong_memory_fta.puml"
  line = 41
  failure_modes = [Communication.MemoryAllocatedInWrongSection]
}

// in_memory_configuration_wrong_fta.puml:21
ScoreReq.RootCause UserProvidedWrongConfiguration {
  title = "User provided wrong configuration"
  diagram = "in_memory_configuration_wrong_fta.puml"
  line = 21
  failure_modes = [Communication.InMemoryConfigurationWrong]
}

// start_find_service_callback_is_redundantly_called_fta.puml:25
ScoreReq.RootCause WatchesAreSetWrongly {
  title = "Watches are set wrongly"
  diagram = "start_find_service_callback_is_redundantly_called_fta.puml"
  line = 25
  failure_modes = [Communication.StartFindServiceCallbackCalledUnexpectedly]
}

// does_not_free_resources_after_usage_fta.puml:22
ScoreReq.RootCause WritingStateChangeIsNotWorking {
  title = "Writing State change is not working"
  diagram = "does_not_free_resources_after_usage_fta.puml"
  line = 22
  failure_modes = [Communication.SendingEventDoesNotFreeResources]
}

// service_is_found_but_does_not_exist_fta.puml:27
ScoreReq.RootCause WrongAcl {
  title = "Wrong ACL"
  diagram = "service_is_found_but_does_not_exist_fta.puml"
  line = 27
  failure_modes = [Communication.ServiceIsFoundButDoesNotExist]
}

// callback_not_invoked_despite_samples_available_fta.puml:28
ScoreReq.RootCause WrongAclConfigurationForShmSegments {
  title = "Wrong ACL configuration for SHM segments"
  diagram = "callback_not_invoked_despite_samples_available_fta.puml"
  line = 28
  failure_modes = [Communication.CallbackNotInvokedDespiteSamplesAvailable]
}

// skeleton_not_offered_fta.puml:24
ScoreReq.RootCause WrongDirectoryStructure {
  title = "Wrong Directory Structure"
  diagram = "skeleton_not_offered_fta.puml"
  line = 24
  failure_modes = [Communication.ServiceNotOffered]
}

// skeleton_not_offered_fta.puml:25
ScoreReq.RootCause WrongMarkerFileName {
  title = "Wrong Marker File name"
  diagram = "skeleton_not_offered_fta.puml"
  line = 25
  failure_modes = [Communication.ServiceNotOffered]
}

// wrong_resources_freed_fta.puml:25
ScoreReq.RootCause WrongMemoryResourceProxy {
  title = "Wrong memory resource proxy"
  diagram = "wrong_resources_freed_fta.puml"
  line = 25
  failure_modes = [Communication.WrongResourcesFreed]
}

// service_is_found_but_does_not_exist_fta.puml:26
ScoreReq.RootCause WrongName {
  title = "Wrong Name"
  diagram = "service_is_found_but_does_not_exist_fta.puml"
  line = 26
  failure_modes = [Communication.ServiceIsFoundButDoesNotExist]
}

// wrong_resources_freed_fta.puml:23
ScoreReq.RootCause WrongNameOfSharedMemorySegment {
  title = "Wrong name of shared memory segment"
  diagram = "wrong_resources_freed_fta.puml"
  line = 23
  failure_modes = [Communication.WrongResourcesFreed]
}

// wrong_service_found_fta.puml:25
ScoreReq.RootCause WrongPathResolvedFromInstanceidentifier {
  title = "Wrong path resolved from InstanceIdentifier"
  diagram = "wrong_service_found_fta.puml"
  line = 25
  failure_modes = [Communication.WrongServiceFound]
}

// service_is_found_but_does_not_exist_fta.puml:25
ScoreReq.RootCause WrongProvider {
  title = "Wrong Provider"
  diagram = "service_is_found_but_does_not_exist_fta.puml"
  line = 25
  failure_modes = [Communication.ServiceIsFoundButDoesNotExist]
}

// service_not_found_fta.puml:21
ScoreReq.RootCause WrongServiceDiscoveryMarkerFileSearchedFor {
  title = "Wrong service discovery marker file searched for"
  diagram = "service_not_found_fta.puml"
  line = 21
  failure_modes = [Communication.ServiceNotFound]
}

// returns_wrong_data_fta.puml:23
ScoreReq.RootCause WrongSlotReferenced {
  title = "Wrong slot referenced"
  diagram = "returns_wrong_data_fta.puml"
  line = 23
  failure_modes = [Communication.ReturnsWrongData]
}

// callback_not_invoked_despite_samples_available_fta.puml:25
ScoreReq.RootCause WrongValueInsertedSlotStatus {
  title = "Wrong value inserted"
  diagram = "callback_not_invoked_despite_samples_available_fta.puml"
  line = 25
  failure_modes = [Communication.CallbackNotInvokedDespiteSamplesAvailable]
}

// callback_not_invoked_despite_samples_available_fta.puml:30
ScoreReq.RootCause WrongValueInsertedTimestamp {
  title = "Wrong value inserted"
  diagram = "callback_not_invoked_despite_samples_available_fta.puml"
  line = 30
  failure_modes = [Communication.CallbackNotInvokedDespiteSamplesAvailable]
}

// subscribe_with_wrong_max_sample_count_fta.puml:21
ScoreReq.RootCause WrongValueIsPassedToMessagePassingLibrary {
  title = "Wrong value is passed to message passing library"
  diagram = "subscribe_with_wrong_max_sample_count_fta.puml"
  line = 21
  failure_modes = [Communication.SubscribeWithWrongMaxSampleCount]
}
